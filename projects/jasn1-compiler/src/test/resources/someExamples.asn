SOME_EXAMPLE DEFINITIONS IMPLICIT TAGS ::=
BEGIN

TaggedSeqOf ::= SEQUENCE OF [3] EXPLICIT INTEGER




SequenceOfAll ::= SEQUENCE {

	myInteger [30] INTEGER OPTIONAL,
	myInteger2 [31] IMPLICIT INTEGER,
	myBoolean BOOLEAN,
	bitString BIT STRING,
	enumerated ENUMERATED {test1(1), test2(2)},
	generalizedTime GeneralizedTime,
	myNull NULL,
	objectIdentifier OBJECT IDENTIFIER,
	octetString OCTET STRING,
	real REAL,
	testIntegerWithValues IntegerWithValues,
	testOctetStringWithSize OctetStringWithSize,
	testSequenceWithSize SequenceWithSize,
	

	--all the strings
	bmpString BMPString,
	generalString GeneralString,
	graphicString GraphicString,
	iA5String IA5String,
	numericString NumericString,
	printableString PrintableString,
	teletexString TeletexString,
	universalString UniversalString,
	utf8String UTF8String,
	videotexString VideotexString,
	visibleString VisibleString,
	any [9] EXPLICIT ANY,
	my-sequence My-Sequence,
	my-choice My-Choice
}

My-Sequence ::= [APPLICATION 3] IMPLICIT SEQUENCE {
	implVisibleString [0] IMPLICIT ImplVisibleString
}

My-Choice ::= CHOICE {
	my-choice2 My-Choice2,
	myboolean BOOLEAN
}

My-Choice2 ::= CHOICE {
	CHOICE {
		test INTEGER
	},
	INTEGER,
	myboolean BOOLEAN,
	CHOICE {
		test INTEGER,
		test2 BOOLEAN
	}
}

--not supported yet
--MyBoxedSequence ::= [APPLICATION 2] IMPLICIT MySequence

ImplInteger	::= [APPLICATION 3] IMPLICIT INTEGER
ImplBoolean	::= [APPLICATION 3] IMPLICIT BOOLEAN
ImplBitString	::= [APPLICATION 3] IMPLICIT BIT STRING
ImplEnum	::= [APPLICATION 3] IMPLICIT ENUMERATED {test1(1),test2(2)}
ImplGeneralizedTime	::= [APPLICATION 3] IMPLICIT GeneralizedTime
ImplNull	::= [APPLICATION 3] IMPLICIT NULL
ImplObjectIdentifier	::= [APPLICATION 3] IMPLICIT OBJECT IDENTIFIER
ImplOctetString	::= [APPLICATION 3] IMPLICIT OCTET STRING
ImplReal	::= [APPLICATION 3] IMPLICIT REAL

ImplBMPString ::= [APPLICATION 3] IMPLICIT BMPString
ImplGeneralString ::= [APPLICATION 3] IMPLICIT GeneralString
ImplGraphicString ::= [APPLICATION 3] IMPLICIT GraphicString
ImplIA5String ::= [APPLICATION 3] IMPLICIT IA5String
ImplNumericString ::= [APPLICATION 3] IMPLICIT NumericString
ImplPrintableString ::= [APPLICATION 3] IMPLICIT PrintableString
ImplTeletexString ::= [APPLICATION 3] IMPLICIT TeletexString
ImplUniversalString ::= [APPLICATION 3] IMPLICIT UniversalString
ImplUTF8String ::= [APPLICATION 3] IMPLICIT UTF8String
ImplVideotexString ::= [APPLICATION 3] IMPLICIT VideotexString
ImplVisibleString ::= [APPLICATION 3] IMPLICIT VisibleString

IntegerWithValues ::= INTEGER {
	acceptance (0),
	user_rejection (1),
	provider_rejection (2)
}

OctetStringWithSize ::= OCTET STRING (SIZE (8))

OctetStringWithSize2 ::= OCTET STRING (SIZE (8..12))


SequenceWithSize ::= [APPLICATION 9] IMPLICIT SEQUENCE (SIZE (8..12)) OF ImplVisibleString

SequenceWithSize2 ::= [APPLICATION 9] IMPLICIT SEQUENCE (SIZE (8)) OF ImplVisibleString

SequenceWithSize3 ::= [APPLICATION 9] IMPLICIT SEQUENCE SIZE (8..12) OF ImplVisibleString

SequenceWithSize4 ::= [APPLICATION 9] IMPLICIT SEQUENCE SIZE (8) OF ImplVisibleString

IdentifierString        ::=   VisibleString (FROM (ALL EXCEPT " "))

END
